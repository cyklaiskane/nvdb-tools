FME workspace 210520_cykelbarhetsklassning_nvdb_till_cyklaiskane.fmw

Parameters:
- INDATA_ADT_till_SDT =
- INDATA_NVDB_homo =
- INDATA_NVDB_trafik_shp =
- INDATA_tatorter =
- UTDATA_DATASET =

Creator
    GEOMTYPE = Geometry Object
    NUM = 1
    CREATED -> Tester
    CREATED -> NVDB_Vägdata [INITIATOR]
    CREATED -> SCB_Tätorter [INITIATOR]

Bookmark: INDATA: NVDB vägnät
Note: Indata: / Beställs via Lastkajen (Trafikverket) / Homogeniserad geodatabas med följande attribut: / 1. Bro och tunnel/Konstruktion* (Konst_190) / 2.Driftsbidrag statligt/Vägdelsnr / (Vagde_10379) / 3. Driftbidrag statligt/Vägnr / (Vagnr_10370) / 4. Funktionell vägklass/Klass / (Klass_181) / 5. Färjeled* / (Farjeled) / 6. Förbjuden färdriktning, Framriktning* / (F_ForbjudenFardriktning) / 7. Förbjuden färdriktning, Bakriktning* / (B_ForbjudenFardriktning) / 8. Gatunamn/Namn* / (Namn_130) / 9. GCM-vägtyp/GCM-typ / (GCM_t_502) / 10. Hastighetsgräns/Högsta tillåtna hastighet, Framriktning / (F_Hogst_225) / 11. Hastighetsgräns/Högsta tillåtna hastighet, Bakriktning / (B_Hogst_225) / 12. Motortrafikled / (Motortrafikled) / 13. Motorväg / (Motorvag) / 14. Slitlager/Slitlagertyp / (Slitl_152) / 15. Trafik/ÅDT fordon / (ADT_f_117) / 16. Vägbredd/Bredd / (Bredd_156) / 17. Väghållare/Väghållartyp / (Vagha_6) / 18. Vägtrafiknät/Nättyp / (Vagtr_474) / *Används inte av klassningen utan för vidareutveckling av ruttningstjänster.
NVDB_Vägdata: FeatureReader
    ATTRS_TO_EXPOSE = ADT_f_117 B_ForbjudenFardriktning B_Hogst_225 Bredd_156 F_ForbjudenFardriktning F_Hogst_225 Farjeled FROM_MEASURE GCM_t_502 Klass_181 Konst_190 Motortrafikled Motorvag Namn_130 OBJECTID ROUTE_ID Shape_Length Slitl_152 TO_MEASURE Vagde_10379 Vagha_6 Vagnr_10370 Vagtr_474 ADT_f_117 B_ForbjudenFardriktning B_Hogst_225 B_Hogst_225_resolved Bredd_156 F_ForbjudenFardriktning F_Hogst_225 F_Hogst_225_resolved Farjeled FROM_MEASURE GCM_t_502 GCM_t_502_resolved Klass_181 Klass_181_resolved Konst_190 Konst_190_resolved Motortrafikled Motorvag Namn_130 OBJECTID ROUTE_ID Shape_Length Slitl_152 Slitl_152_resolved TO_MEASURE Vagde_10379 Vagha_6 Vagha_6_resolved Vagnr_10370 Vagtr_474 Vagtr_474_resolved
    ATTR_ACCUM_MODE = Only Use Result
    COMBINE_GEOM = Use Result
    DATASET = C:\Temp_C\fme_cykel\lastkajen_data\Cykelbarhetsklassning.gdb
    FORMAT = GEODATABASE_FILE
    GEODATABASE_FILE_ALIAS_MODE = NONE
    GEODATABASE_FILE_CACHE_MULTIPATCH_TEXTURES = yes
    GEODATABASE_FILE_CHECK_SIMPLE_GEOM = no
    GEODATABASE_FILE_CREATE_FEATURE_TABLES_FROM_DATA = Yes
    GEODATABASE_FILE_FEATURE_READ_MODE = Features
    GEODATABASE_FILE_IGNORE_NETWORK_INFO = yes
    GEODATABASE_FILE_IGNORE_RELATIONSHIP_INFO = yes
    GEODATABASE_FILE_MERGE_FEAT_LINKED_ANNOS = no
    GEODATABASE_FILE_QUERY_FEATURE_TYPES_FOR_MERGE_FILTERS = Yes
    GEODATABASE_FILE_READ_THREE_POINT_ARCS = no
    GEODATABASE_FILE_RESOLVE_DOMAINS = yes
    GEODATABASE_FILE_RESOLVE_SUBTYPE_NAMES = yes
    GEODATABASE_FILE_SPLIT_COMPLEX_ANNOS = no
    GEODATABASE_FILE_SPLIT_COMPLEX_EDGES = no
    GEODATABASE_FILE_SPLIT_MULTI_PART_ANNOS = no
    GEODATABASE_FILE_STRIP_GUID_GLOBALID_BRACES = no
    GEODATABASE_FILE_TRANSLATE_SPATIAL_DATA_ONLY = no
    GEODATABASE_FILE_USE_SEARCH_ENVELOPE = NO
    INTERACT = <No Spatial Filter>
    OUTPUT_FEATURES_DISPLAY = Schema and Data Features
    <OTHER> -> AttributeManager_2
AttributeManager_2
    ATTR_TABLE:
      SET_TO B_Hogst_225 = FME_CONDITIONAL:DEFAULT_VALUE'_FME_NO_OP_'BOOL_OP;OR;COMPOSITE_TEST;1;TEST @Value(B_Hogst_225) = gångfart'5'FME_NUM_CONDITIONS2___
      SET_TO F_Hogst_225 = FME_CONDITIONAL:DEFAULT_VALUE'_FME_NO_OP_'BOOL_OP;OR;COMPOSITE_TEST;1;TEST @Value(F_Hogst_225) = gångfart'5'FME_NUM_CONDITIONS2___
      SET_TO TS_klass = FME_NULL_VALUE
    -> ExpressionEvaluator
Note: Gör om hastighet (fram och bak) till maxvärde
ExpressionEvaluator
    ACTION = Create New Attribute
    EXPRESSION = @max(@Value(F_Hogst_225), @Value(B_Hogst_225))
    VAL_ATTR = MaxHastighet
    -> TestFilter_2

Bookmark: Testfiltrar
TestFilter_2
    DEFAULT_VALUE = <UNFILTERED>
    TEST_LIST:
      "BOOL_OP,OR,COMPOSITE_TEST,""""""1"""""",TEST_CLAUSE,TEST @Value(Farjeled) = -1",färjeled,"BOOL_OP,OR,COMPOSITE_TEST,""""""1 OR 2"""""",TEST_CLAUSE,CASE_INSENSITIVE_TEST @Value(Vagtr_474) = 2
      CASE_INSENSITIVE_TEST @Value(Vagtr_474) = 4",cykelväg,"BOOL_OP,OR,COMPOSITE_TEST,""""""1 OR 2"""""",TEST_CLAUSE,NUM_TEST @Value(Motorvag) = -1
      NUM_TEST @Value(Motortrafikled) = -1",cykelförbud,"BOOL_OP,AND,COMPOSITE_TEST,""""""1 AND 2 AND 3 AND 4"""""",TEST_CLAUSE,TEST Vagde_10379 ATTRIBUTE_VALUE_NULL ""
      TEST Vagnr_10370 ATTRIBUTE_VALUE_NULL ""
      TEST @Value(Vagha_6) = 3
      TEST @Value(Slitl_152) = 2",oklassificerade grusvägar,"BOOL_OP,AND,COMPOSITE_TEST,""""""1 AND 2"""""",TEST_CLAUSE,CASE_INSENSITIVE_TEST @Value(Vagtr_474) = 1
      TEST MaxHastighet ATTRIBUTE_VALUE_NULL """,allmän väg utan hastighet,"BOOL_OP,OR,COMPOSITE_TEST,""""""1"""""",TEST_CLAUSE,TEST ADT_f_117 ATTRIBUTE_HAS_A_VALUE """,har ÅDT
    färjeled -> Junction_8
    cykelväg -> TestFilter
    cykelförbud -> Junction_3
    oklassificerade grusvägar -> Junction_6
    allmän väg utan hastighet -> Junction_8
    har ÅDT -> FeatureJoiner [LEFT]
    <UNFILTERED> -> TestFilter_vägklass
Note: Direkt ut
Junction_8
    -> Junction_9
Note: B5
Junction_3
    -> Junction_4
Note: G2
Junction_6
    -> Junction_7

Bookmark: Klassificera cykelvägar
TestFilter
    DEFAULT_VALUE = Cykelväg (C1)
    TEST_LIST = "BOOL_OP,OR,COMPOSITE_TEST,""""""1"""""",TEST_CLAUSE,TEST @Value(Vagtr_474) = 4",Gångväg,"BOOL_OP,OR,COMPOSITE_TEST,""""""1"""""",TEST_CLAUSE,TEST @Value(GCM_t_502) = 2",Cykelfält (C3),"BOOL_OP,OR,COMPOSITE_TEST,""""""1"""""",TEST_CLAUSE,TEST @Value(Slitl_152) = 2",Cykelväg, grus (C2)
    Gångväg -> Junction_13
    Cykelfält (C3) -> AttributeManager_C3
    Cykelväg, grus (C2) -> AttributeManager_C2
    Cykelväg (C1) -> AttributeManager_C1
Note: Till: Utdata
Junction_13
    -> Junction_14
AttributeManager_C3
    ATTR_TABLE = SET_TO TS_klass = C3
    -> Junction_18
AttributeManager_C2
    ATTR_TABLE = SET_TO TS_klass = C2
    -> Junction_18
AttributeManager_C1
    ATTR_TABLE = SET_TO TS_klass = C1
    -> Junction_18
Note: Till: Utdata
Junction_18
    -> Junction_19

Bookmark: Outputs
Note: Gångvägar
Junction_14
    -> AttributeKeeper
Note: Cykelvägar
Junction_19
    -> AttributeKeeper
Note: Oklassade vägar
Junction_9
    -> AttributeKeeper
AttributeKeeper
    CREATE_BULK_MODE_FEATURES = NO
    KEEP_ATTRS = ADT_f_117,B_ForbjudenFardriktning,B_Hogst_225,Bredd_156,F_ForbjudenFardriktning,F_Hogst_225,Farjeled,FROM_MEASURE,GCM_t_502,Motortrafikled,Motorvag,Namn_130,ROUTE_ID,Shape_Length,TO_MEASURE,TS_klass,Vagde_10379,Vagnr_10370,IK_NR,Konst_190_resolved,Slitl_152_resolved,Vagha_6_resolved,Vagtr_474_resolved,Klass_181,Konst_190,Slitl_152,Vagha_6,Vagtr_474
    -> AttributeRenamer
AttributeRenamer
    ATTR_TABLE:
      RENAME_SET_DEFAULT Konst_190_resolved > Konst_190_txt
      RENAME_SET_DEFAULT Slitl_152_resolved > Slitl_152_txt
      RENAME_SET_DEFAULT Vagha_6_resolved > Vagha_6_txt
      RENAME_SET_DEFAULT Vagtr_474_resolved > Vagtr_474_txt
    MISSING_INPUT_ATTRS = REMOVE
    -> FeatureWriter [Output]

Bookmark: Ange cykelbarhetsklass för blandtrafik (B1-B5 samt grusvägar G1-G2)
Junction_4
    -> Ange_Klass_B5
Ange_Klass_B5: AttributeManager
    ATTR_TABLE = SET_TO TS_klass = B5
    -> Tester_grusväg_dålig
Note: Från TestFilter_vägklass
Junction_2
    -> Ange_Klass_B4
Ange_Klass_B4: AttributeManager
    ATTR_TABLE = SET_TO TS_klass = B4
    -> Tester_grusväg_dålig
Note: Ange cykelbarhetsklass / B1 - Mycket God / B2 - God / B3 - Tveksam / B4 - Olämplig / B5 - Förbjuden
Note: Från: Test för vägar utan ÅDT
Junction_16
    -> Ange_Klass_B2
Ange_Klass_B2: AttributeManager
    ATTR_TABLE = SET_TO TS_klass = B2
    -> Tester_MycketGod
Junction_10
    -> Ange_Klass_B3
Ange_Klass_B3: AttributeManager
    ATTR_TABLE = SET_TO TS_klass = B3
    -> Tester_grusväg_dålig

Bookmark: Klassificera grusvägar
Note: Oklassificerade grusvägar
Junction_7
    -> Ange_Klass_G2
Note: Filtrerar grusvägar från belagda vägar.
Tester_grusväg_bra
    BOOL_OP = OR
    COMPOSITE_TEST = 1
    TEST_CLAUSE = TEST @Value(Slitl_152) = 2
    TEST_MODE = TEST
    PASSED -> Ange_Klass_G1
    FAILED -> AttributeKeeper
Ange_Klass_G1: AttributeManager
    ATTR_TABLE = SET_TO TS_klass = G1
    -> AttributeKeeper
Note: Filtrerar grusvägar från belagda vägar.
Tester_grusväg_dålig
    BOOL_OP = OR
    COMPOSITE_TEST = 1
    TEST_CLAUSE = TEST @Value(Slitl_152) = 2
    TEST_MODE = TEST
    PASSED -> Ange_Klass_G2
    FAILED -> AttributeKeeper
Ange_Klass_G2: AttributeManager
    ATTR_TABLE = SET_TO TS_klass = G2
    -> AttributeKeeper

Bookmark: Test för vägar utan ÅDT
Note: Alla vägar med hastighet på 90km/t eller högre, eller klass 0-3 klassas som olämpliga.
TestFilter_vägklass
    DEFAULT_VALUE = <UNFILTERED>
    TEST_LIST:
      "BOOL_OP,OR,COMPOSITE_TEST,""""""1 OR 2"""""",TEST_CLAUSE,NUM_TEST @Value(MaxHastighet) >= 90
      NUM_TEST @Value(Klass_181) < 4",olämplig,"BOOL_OP,OR,COMPOSITE_TEST,""""""1"""""",TEST_CLAUSE,NUM_TEST @Value(MaxHastighet) <= 30",<= 30,"BOOL_OP,AND,COMPOSITE_TEST,""""""1 AND 2"""""",TEST_CLAUSE,NUM_TEST @Value(Klass_181) = 4
      NUM_TEST @Value(MaxHastighet) > 40",4 och > 40,"BOOL_OP,AND,COMPOSITE_TEST,""""""1 AND 2"""""",TEST_CLAUSE,NUM_TEST @Value(Klass_181) = 4
      NUM_TEST @Value(MaxHastighet) <= 40",4 och <= 40,"BOOL_OP,OR,COMPOSITE_TEST,""""""1"""""",TEST_CLAUSE,NUM_TEST @Value(Klass_181) IN 5,6",5, 6,"BOOL_OP,OR,COMPOSITE_TEST,""""""1"""""",TEST_CLAUSE,NUM_TEST @Value(Klass_181) >= 7",7, 8, 9
    olämplig -> Junction
    <= 30 -> Junction_12
    4 och > 40 -> Junction
    4 och <= 40 -> Junction_5
    5, 6 -> SpatialFilter [Candidate]
    7, 8, 9 -> Junction_15
Note: B4
Note: Cykelbarhetsklassen för vägklass 5 och 6 beror på tätorts storlek och hastighetsgränsen. Vägklass 4 tar också hänsyn till hastighetsgränsen. Vägklass 0-3 och 7-9 klassas som olämplig respektive god.
Junction
    -> Junction_2
Note: B1
Junction_12
    -> Junction_11
Note: Filtrerar tätorter med fler än 15000 invånare.
Tester_Befolkning_15k
    BOOL_OP = OR
    COMPOSITE_TEST = 1
    TEST_CLAUSE = TEST @Value(BEF) >= 15000
    TEST_MODE = TEST
    PASSED -> SpatialFilter [Filter]
Note: Filtrerar Klass 5/6 vägar som är inom och utanför tätorter med fler än 15000 invånare.
SpatialFilter
    AGGREGATE_HANDLING = Yes
    BASE_TYPE = Multiple Filters
    CURVE_BOUNDARY_RULE_PARAM = Default Rule
    PASS_CRITERIA = Pass Against One Filter
    PREDICATES = INTERSECTS
    USE_BOUNDING_BOX = No
    PASSED -> Junction_5
    FAILED -> Tester_40kmt
Note: Filtrerar vägar med en hastighetsgräns på 40km/h eller lägre
Tester_40kmt
    BOOL_OP = OR
    COMPOSITE_TEST = 1
    TEST_CLAUSE = TEST @Value(MaxHastighet) <= 40
    TEST_MODE = TEST
    PASSED -> Junction_15
    FAILED -> Junction_5
Note: B2
Junction_15
    -> Junction_16
Note: B3
Junction_5
    -> Junction_10

Bookmark: Skapa trafiksäkerhetsklass "Mycket God" (B1)
Note: Vägar med hastighet < 30
Junction_11
    -> Ange_Klass_B1
Note: Vägar som klassas som "God=1" med ÅDT <= 250 eller med vägbredd <= 3,5 klassas om till "Mycket god=B1".
Tester_MycketGod
    BOOL_OP = COMPOSITE
    COMPOSITE_TEST:
      ( NOT 1 AND ( 2 OR 3 )
       ) OR ( 4 AND 5 AND 6 )
    TEST_CLAUSE:
      TEST ADT_modified ATTRIBUTE_VALUE_NULL ""
      NUM_TEST @Value(ADT_modified) <= 250
      NUM_TEST @Value(Bredd_156) <= 3.5
      TEST ADT_modified ATTRIBUTE_VALUE_NULL ""
      NUM_TEST @Value(MaxHastighet) <= 30
      NUM_TEST @Value(Klass_181) IN 7,8,9
    TEST_MODE = PER_TEST
    PASSED -> Ange_Klass_B1
    FAILED -> Tester_grusväg_bra
Ange_Klass_B1: AttributeManager
    ATTR_TABLE = SET_TO TS_klass = B1
    -> Tester_grusväg_bra

Bookmark: INDATA: SDT
Note: Indata: / Beställs via Lastkajen (Trafikverket) / Shapefil med: Vägtrafikdata/Trafik / Följande attribut i shapefilen används: / 1. RLID / 2. AVSITTIDET / RLID används för att koppla ihop lagret med den homogeniserade geodatabasen. / AVSITTIDET används för att koppla ihop SDT-data med vägnätet. / Shapefilen krävs om man ska använda SDT i klassificeringen eftersom SDT-värden inte är tillgänglig via den homogeniserade geodatabasen. SDT-värden beräknas med hjälp av ÅDT samt ett indexvärde som kopplas till vägnätet via AVSITTIDET. AVSITTIDET är inte heller tillgänglig via den homogeniserade geodatabasen. / Beställs via Trafikverket / Excelfil med: ÅDT-till-SDT Indexkurvor / Följade kolumner används: / 1. AVSN_ID / 2. IK_NR / AVSN_ID kopplas ihop med AVSITTIDET för att identifiera väglänken som SDT gäller för. IK_NR används för att beräkna om ÅDT till SDT.
Note: Både NVDB region och ÅDT till SDT måste vara definerade för att aktivera följande läsarna.
Tester
    BOOL_OP = COMPOSITE
    COMPOSITE_TEST = 1 AND 2
    TEST_CLAUSE:
      CASE_INSENSITIVE_TEST $(INDATA_ADT_till_SDT) ENDS_WITH .xlsx
      CASE_INSENSITIVE_TEST $(INDATA_NVDB_trafik_shp) ENDS_WITH .shp
    TEST_MODE = CASE_INSENSITIVE_TEST
    PASSED -> ADT_to_SDT [INITIATOR]
    PASSED -> NVDB_Trafik [INITIATOR]
NVDB_Trafik: FeatureReader
    ATTRS_TO_EXPOSE = RLID AVSITTIDET
    ATTR_ACCUM_MODE = Only Use Result
    COMBINE_GEOM = Use Result
    DATASET = $(INDATA_NVDB_trafik_shp)
    FORMAT = SHAPEFILE
    INTERACT = <No Spatial Filter>
    OUTPUT_FEATURES_DISPLAY = Schema and Data Features
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = MISSING
    SHAPEFILE_READ_NUMERIC_PADDING_AS = ZERO
    SHAPEFILE_REPORT_BAD_GEOMETRY = No
    SHAPEFILE_TRIM_PRECEDING_SPACES = Yes
    SHAPEFILE_USE_SEARCH_ENVELOPE = NO
    <OTHER> -> InlineQuerier_Beräkna_SDT [Trafik]
ADT_to_SDT: FeatureReader
    ATTRS_TO_EXPOSE = AVSN_ID IK_NR
    ATTR_ACCUM_MODE = Only Use Result
    COMBINE_GEOM = Use Result
    DATASET = $(INDATA_ADT_till_SDT)
    FORMAT = XLSXR
    INTERACT = <No Spatial Filter>
    OUTPUT_FEATURES_DISPLAY = Schema and Data Features
    XLSXR_ALLOW_DOLLAR_SIGNS = YES
    XLSXR_CASE_SENSITIVE_FEATURE_TYPES = YES
    XLSXR_CREATE_FEATURE_TABLES_FROM_DATA = Yes
    XLSXR_EXCEL_COL_NAMES = YES
    XLSXR_EXPAND_MERGED_CELLS = Yes
    XLSXR_FORCE_DATETIME = NO
    XLSXR_QUERY_FEATURE_TYPES_FOR_MERGE_FILTERS = Yes
    XLSXR_READ_BLANK_AS = Missing
    XLSXR_SCAN_SCHEMA_IF_DYNAMIC = No
    XLSXR_STRIP_SHEETNAME_SPACES = YES
    XLSXR_USE_SCHEMA_OTHER_FILES = No
    <OTHER> -> InlineQuerier_Beräkna_SDT [SDT]

Bookmark: Test för vägar med ÅDT
Note: Kopplar SDT-data till trafikdata med hjälp av SQL.
InlineQuerier_Beräkna_SDT
    QUERY_DEF:
      network,SELECT
          b.RLID,
          max((IK_NR % 100) / 10.0) as ADT_to_SDT,
          a.IK_NR
      FROM
          "SDT" a
      JOIN
          "Trafik" b
      ON
          a.AVSN_ID = b.AVSITTIDET
      WHERE
          IK_NR < 90000
      GROUP BY
          b.RLID,FIRST
    QUERY_SCHEMA = network,RLID,varchar(200),ADT_to_SDT,,IK_NR,integer
    TABLE_DEF = SDT,AVSN_ID,integer,IK_NR,integer,Trafik,OBJECTID,varchar(200),RLID,varchar(200),AVSITTIDET,varchar(200)
    network -> FeatureJoiner [RIGHT]
FeatureJoiner
    ATTR_CONFLICT_RES = Use Left
    GEOMETRY_HANDLING = Use Left
    JOIN_KEYS = ROUTE_ID RLID AUTO
    JOIN_MODE = Left
    JOINED -> ExpressionEvaluator_Beräkna_ADT
Note: Ersätter ÅDT-värdet med SDT-värdet om SDT är högre än ÅDT.
ExpressionEvaluator_Beräkna_ADT
    ACTION = Create New Attribute
    EXPRESSION = @round(@Value(ADT_f_117) * @Value(ADT_to_SDT))
    VAL_ATTR = ADT_modified
    -> TestFilter_lämplighet
Note: Klassningen är baserad på Trafikverkets riktlinjer för vägvisning.
TestFilter_lämplighet
    DEFAULT_VALUE = god (B2)
    TEST_LIST:
      "BOOL_OP,COMPOSITE,COMPOSITE_TEST,""""""1 OR ( 2 AND 3 ) OR ( 4 AND 5 ) OR ( 6 AND 7 )"""""",TEST_CLAUSE,NUM_TEST @Value(MaxHastighet) > 80
      NUM_TEST @Value(ADT_modified) >= 2500
      NUM_TEST @Value(MaxHastighet) > 40
      NUM_TEST @Value(ADT_modified) >= 2000
      NUM_TEST @Value(MaxHastighet) > 60
      NUM_TEST @Value(ADT_modified) >= 1000
      NUM_TEST @Value(MaxHastighet) > 70",olämplig (B4),"BOOL_OP,COMPOSITE,COMPOSITE_TEST,""""""1 OR ( 2 AND 3 ) OR ( 4 AND 5 ) OR ( 6 AND 7 )"""""",TEST_CLAUSE,NUM_TEST @Value(MaxHastighet) > 70
      NUM_TEST @Value(ADT_modified) >= 1000
      NUM_TEST @Value(MaxHastighet) > 60
      NUM_TEST @Value(ADT_modified) >= 2000
      NUM_TEST @Value(MaxHastighet) > 40
      NUM_TEST @Value(ADT_modified) >= 2500
      NUM_TEST @Value(MaxHastighet) > 30",tveksam (B3)
    olämplig (B4) -> Ange_Klass_B4
    tveksam (B3) -> Ange_Klass_B3
    god (B2) -> Ange_Klass_B2

Bookmark: INDATA: SCB Tätorter
Note: Indata: / Hämtas via SCB:s hemsida / Shapefil med: Tätortsavgränsning / Följande attribut i shapefilen används: / 1. BEF / BEF innehåller uppgifter om tätortens befolkningsmängd. Den används för att skilja mellan vägar utan ÅDT som har samma funktionell vägklass. Vägar med samma vägklass i mindre tätorter anses vara mer cykelbara än i större tätorter.
SCB_Tätorter: FeatureReader
    ATTRS_TO_EXPOSE = BEF
    ATTR_ACCUM_MODE = Only Use Result
    COMBINE_GEOM = Use Result
    DATASET = $(INDATA_tatorter)
    FORMAT = SHAPEFILE
    INTERACT = <No Spatial Filter>
    OUTPUT_FEATURES_DISPLAY = Schema and Data Features
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = MISSING
    SHAPEFILE_READ_NUMERIC_PADDING_AS = ZERO
    SHAPEFILE_REPORT_BAD_GEOMETRY = No
    SHAPEFILE_TRIM_PRECEDING_SPACES = Yes
    SHAPEFILE_USE_SEARCH_ENVELOPE = NO
    <OTHER> -> Tester_Befolkning_15k

Bookmark: GPKG Writer
Note: Skriver till en Geopackage-fil ett dataset med ingående uppgifter från NVDB samt TS_Klass, vilket innehåller cykelbarhetsklassningen.
FeatureWriter
    COORDSYS = EPSG:3006
    DATASET = $(UTDATA_DATASET)
    DATASET_ATTR = _dataset
    FEATURE_TYPE_LIST_ATTR = _feature_type
    FORMAT = OGCGEOPACKAGE
    OGCGEOPACKAGE_COORDINATE_SYSTEM_GRANULARITY = FEATURE_TYPE
    OGCGEOPACKAGE_DESTINATION_DATASETTYPE_VALIDATION = Yes
    OGCGEOPACKAGE_ENCODE_FEATURE_TYPE_AND_ATTR_NAMES = YES
    OGCGEOPACKAGE_ENFORCE_GEOMETRY_COLUMN_CONSTRAINTS = YES
    OGCGEOPACKAGE_OVERWRITE_DATASET = NO
    OGCGEOPACKAGE_TRANSACTION_SIZE = 5000
    OGCGEOPACKAGE_WRITE_NULLS = YES
    TOTAL_FEATURES_WRITTEN_ATTR = _total_features_written
    SUMMARY -> PythonCaller
Note: Skapar olika vyer i Geopackage-filen
PythonCaller
    PYTHONSOURCE:
      import fme
      import fmeobjects
      import sqlite3


      class FeatureProcessor(object):
          def __init__(self):
              pass
          def input(self,feature):
              db_file = feature.getAttribute("_dataset")
              with sqlite3.connect(db_file) as db:
                  db.executescript("""
      CREATE VIEW IF NOT EXISTS
        cykelnat (id,geom,ROUTE_ID,FROM_MEASURE,TO_MEASURE,TS_klass) AS
      SELECT id,geom,ROUTE_ID,FROM_MEASURE,TO_MEASURE,TS_klass
      FROM network
      WHERE Vagtr_474 = 2;

      INSERT OR REPLACE INTO
        gpkg_contents (table_name,data_type,identifier,min_x,min_y,max_x,max_y,srs_id)
      SELECT "cykelnat",data_type,"cykelnat",min_x,min_y,max_x,max_y,srs_id
      FROM gpkg_contents
      WHERE identifier = "network";

      INSERT OR REPLACE INTO
        gpkg_geometry_columns (table_name,column_name,geometry_type_name,srs_id,z,m)
      SELECT "cykelnat","geom",geometry_type_name,srs_id,z,m
      FROM gpkg_geometry_columns
      WHERE table_name = "network";
      """)

                  db.executescript("""
      CREATE VIEW IF NOT EXISTS
        vagnat (id,geom,ROUTE_ID,FROM_MEASURE,TO_MEASURE,TS_klass) AS
      SELECT id,geom,ROUTE_ID,FROM_MEASURE,TO_MEASURE,TS_klass
      FROM network
      WHERE Vagtr_474 = 1;

      INSERT OR REPLACE INTO
        gpkg_contents (table_name,data_type,identifier,min_x,min_y,max_x,max_y,srs_id)
      SELECT "vagnat",data_type,"vagnat",min_x,min_y,max_x,max_y,srs_id
      FROM gpkg_contents
      WHERE identifier = "network";

      INSERT OR REPLACE INTO
        gpkg_geometry_columns (table_name,column_name,geometry_type_name,srs_id,z,m)
      SELECT "vagnat","geom",geometry_type_name,srs_id,z,m
      FROM gpkg_geometry_columns
      WHERE table_name = "network";
      """)

                  db.executescript("""
      CREATE VIEW IF NOT EXISTS
        bro_tunnel (id,geom,ROUTE_ID,FROM_MEASURE,TO_MEASURE,TS_klass) AS
      SELECT id,geom,ROUTE_ID,FROM_MEASURE,TO_MEASURE,TS_klass
      FROM network
      WHERE Konst_190 IN (1,2,4);

      INSERT OR REPLACE INTO
        gpkg_contents (table_name,data_type,identifier,min_x,min_y,max_x,max_y,srs_id)
      SELECT "bro_tunnel",data_type,"bro_tunnel",min_x,min_y,max_x,max_y,srs_id
      FROM gpkg_contents
      WHERE identifier = "network";

      INSERT OR REPLACE INTO
        gpkg_geometry_columns (table_name,column_name,geometry_type_name,srs_id,z,m)
      SELECT "bro_tunnel","geom",geometry_type_name,srs_id,z,m
      FROM gpkg_geometry_columns
      WHERE table_name = "network";
      """)

                  db.executescript("""
      CREATE VIEW IF NOT EXISTS
        farjeled (id,geom,ROUTE_ID,FROM_MEASURE,TO_MEASURE,TS_klass) AS
      SELECT id,geom,ROUTE_ID,FROM_MEASURE,TO_MEASURE,TS_klass
      FROM network
      WHERE Farjeled = -1;

      INSERT OR REPLACE INTO
        gpkg_contents (table_name,data_type,identifier,min_x,min_y,max_x,max_y,srs_id)
      SELECT "farjeled",data_type,"farjeled",min_x,min_y,max_x,max_y,srs_id
      FROM gpkg_contents
      WHERE identifier = "network";

      INSERT OR REPLACE INTO
        gpkg_geometry_columns (table_name,column_name,geometry_type_name,srs_id,z,m)
      SELECT "farjeled","geom",geometry_type_name,srs_id,z,m
      FROM gpkg_geometry_columns
      WHERE table_name = "network";
      """)
              self.pyoutput(feature)
          def close(self):
              pass
    PYTHONSYMBOL = FeatureProcessor
    -> PythonCaller_Output
PythonCaller_Output: Inspector
