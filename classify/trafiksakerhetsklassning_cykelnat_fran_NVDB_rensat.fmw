FME workspace trafiksakerhetsklassning_cykelnat_fran_NVDB_rensat.fmw

Parameters:
- färg_cykelväg = 0.0901961,0.235294,0.4   # Färg cykelväg
- färg_förbjuden = 0.772549,0.133333,0.0901961   # Färg förbjuden
- färg_olämplig = 0.772549,0.133333,0.0901961   # Färg olämplig
- färg_tveksam = 0.866667,0.537255,0.560784   # Färg tveksam
- färg_god = 0.439216,0.639216,0.952941   # Färg god
- färg_mycket_god = 0.258824,0.352941,0.952941   # Färg mycket god
- färg_vägnät = 0.2,0.2,0.2   # Färg vägnät
- färg_grusväg = 0.541176,0.329412,0.207843   # Färg grusväg
- linje_cykelfält = dot   # Linje cykelfält
- linje_cykelväg = dash   # Linje cykelväg
- linje_standard = solid   # Linje standard
- DestDataset_GEOPACKAGE = cyklaiskane.gpkg   # GeoPackage File
- SourceDataset_ESRISHAPE_4 = /Users/joakim/Maps/Data/SCB/to2015_sr99tm_region/To2015_Swe99TM.shp   # Source Esri Shapefile(s)
- SourceDataset_XLSXR = $(FME_MF_DIR)adt_to_sdt_index.xlsx   # Source Microsoft Excel File(s)
- SourceDataset_GEOPACKAGE = $(FME_MF_DIR)nvdb_skane_network.gpkg   # GeoPackage File

Readers:
- ESRISHAPE_1: ESRISHAPE from $(SourceDataset_ESRISHAPE_4)
- XLSXR_1: XLSXR from $(SourceDataset_XLSXR)
- GEOPACKAGE_1: GEOPACKAGE from $(SourceDataset_GEOPACKAGE)

Writers:
- GEOPACKAGE_2: GEOPACKAGE to $(DestDataset_GEOPACKAGE) in EPSG:3006

Bookmark: Indata (Vägnät och tätorter)
network (reader GEOPACKAGE_1)
    attributes: route_id text(38), from_measure double, to_measure double, road_type smallint, operator_type smallint, operator_name text, width double, flow mediumint, flow_id mediumint, surface smallint, max_speed smallint, gcm_type smallint, road_name text, road_class smallint, grade_type smallint, subsidy boolean, subsidy_from_date smallint, subsidy_to_date smallint, motorway boolean, motorroad boolean, oneway smallint, road_access text, residential boolean, ts_class smallint, bicycle_restrict mediumint, bicycle_route text, bicycleroad boolean, from_vertex mediumint, to_vertex mediumint
    -> InlineQuerier_Beräkna_SDT [network]
Blad1 (reader XLSXR_1)
    attributes: AVSN_ID number(8,0), FKL number(3,0), PER_TYP number(2,0), FOMDAT date, TILLDAT date, IK_NR number(6,0)
    -> InlineQuerier_Beräkna_SDT [Blad1]
InlineQuerier_Beräkna_SDT
    QUERY_DEF:
      network,SELECT net.*, net.flow * COALESCE(adt.flow_factor, 1.0) as flow_real, NULL as ts_class
      FROM
          "network" net
      LEFT JOIN (
          SELECT
              AVSN_ID as flow_id,
              (IK_NR % 100) / 10.0 as flow_factor
          FROM
              "Blad1"
          WHERE
              IK_NR < 90000
      ) adt
      USING (flow_id);,FIRST
    QUERY_SCHEMA = network,route_id,text,length,float,from_measure,float,to_measure,float,road_type,integer,operator_type,integer,operator_name,text,width,float,flow,integer,flow_id,integer,surface,integer,max_speed,integer,gcm_type,integer,road_name,text,road_class,integer,grade_type,integer,subsidy,integer,subsidy_from_date,integer,subsidy_to_date,integer,motorway,integer,motorroad,integer,cycleroad,integer,network.fme_feature_content,fme_feature_content,flow_real,,ts_class,
    TABLE_DEF = network,route_id,text,length,float,from_measure,float,to_measure,float,road_type,integer,operator_type,integer,operator_name,text,width,float,flow,integer,flow_id,integer,surface,integer,max_speed,integer,gcm_type,integer,road_name,text,road_class,integer,grade_type,integer,subsidy,integer,subsidy_from_date,integer,subsidy_to_date,integer,motorway,integer,motorroad,integer,cycleroad,integer,Blad1,AVSN_ID,integer,FKL,integer,PER_TYP,integer,FOMDAT,text,TILLDAT,text,IK_NR,integer
    network -> NullAttributeMapper
NullAttributeMapper
    ATTRCHOICE = Selected Attributes
    ATTRLIST = oneway bicycle_restrict
    NEW_VALUE = 0
    NULL_TREATMENT = New Value
    SOURCE_ATTR_VAL = Null
    -> TestFilter_2
To2015_Swe99TM (reader ESRISHAPE_1)
    attributes: OBJECTID long, AR char(4), LANSKOD char(2), AREA_HA long, BEF long, KOMMUNKOD char(4), KOMMUNNAMN char(50), TATORTSKOD char(5), TATORT char(50), LAN_NAMN char(50)
    -> Tester_Befolkning

Bookmark: Testfiltrar
TestFilter_2
    DEFAULT_VALUE = <UNFILTERED>
    TEST_LIST:
      "BOOL_OP,OR,COMPOSITE_TEST,""""""1 OR 2"""""",TEST_CLAUSE,CASE_INSENSITIVE_TEST @Value(road_type) = 2
      CASE_INSENSITIVE_TEST @Value(road_type) = 4",cykelväg,"BOOL_OP,AND,COMPOSITE_TEST,""""""1 AND 2"""""",TEST_CLAUSE,CASE_INSENSITIVE_TEST @Value(road_type) = 1
      TEST max_speed ATTRIBUTE_VALUE_NULL """,allmän väg utan hastighet,"BOOL_OP,OR,COMPOSITE_TEST,""""""1 OR 2 OR 3"""""",TEST_CLAUSE,NUM_TEST @Value(motorway) = 1
      NUM_TEST @Value(motorroad) = 1
      NUM_TEST @Evaluate(@Value(oneway) | @Value(bicycle_restrict)) >= 3",cykelförbud,"BOOL_OP,AND,COMPOSITE_TEST,""""""1 AND 2 AND 3"""""",TEST_CLAUSE,TEST subsidy ATTRIBUTE_VALUE_NULL ""
      NUM_TEST @Value(operator_type) = 3
      NUM_TEST @Value(surface) = 2",oklassificerade,"BOOL_OP,OR,COMPOSITE_TEST,""""""1"""""",TEST_CLAUSE,TEST flow_real ATTRIBUTE_HAS_A_VALUE """,har ÅDT
    cykelväg -> AttributeManager_4
    allmän väg utan hastighet -> Junction_8
    cykelförbud -> Junction_3
    oklassificerade -> Junction_8
    har ÅDT -> TestFilter_lämplighet
    <UNFILTERED> -> TestFilter_vägklass
Junction_3
    -> Junction_4
Note: AttributeManager_2 : Input
Junction_8
    -> Junction_9

Bookmark: Cykelvägsklassning
AttributeManager_4
    ATTR_TABLE = SET_TO ts_class = -1
    -> network (writer GEOPACKAGE_2)

Bookmark: Test för vägar med ÅDT
Note: Klassningen använder sig av Trafikverkets riktlinjer för vägvisning.
TestFilter_lämplighet
    DEFAULT_VALUE = god (B2)
    TEST_LIST:
      "BOOL_OP,COMPOSITE,COMPOSITE_TEST,""""""1 OR ( 2 AND 3 ) OR ( 4 AND 5 ) OR ( 6 AND 7 )"""""",TEST_CLAUSE,NUM_TEST @Value(max_speed) > 80
      NUM_TEST @Value(flow_real) >= 2500
      NUM_TEST @Value(max_speed) > 40
      NUM_TEST @Value(flow_real) >= 2000
      NUM_TEST @Value(max_speed) > 60
      NUM_TEST @Value(flow_real) >= 1000
      NUM_TEST @Value(max_speed) > 70",olämplig (B4),"BOOL_OP,COMPOSITE,COMPOSITE_TEST,""""""1 OR ( 2 AND 3 ) OR ( 4 AND 5 ) OR ( 6 AND 7 )"""""",TEST_CLAUSE,NUM_TEST @Value(max_speed) > 70
      NUM_TEST @Value(flow_real) >= 1000
      NUM_TEST @Value(max_speed) > 60
      NUM_TEST @Value(flow_real) >= 2000
      NUM_TEST @Value(max_speed) > 40
      NUM_TEST @Value(flow_real) >= 2500
      NUM_TEST @Value(max_speed) > 30",tveksam (B3)
    olämplig (B4) -> ExpressionEvaluator_Olämplig
    tveksam (B3) -> ExpressionEvaluator_Tveksam
    god (B2) -> ExpressionEvaluator_God

Bookmark: Ange trafiksäkerhetsklass
Junction_4
    -> ExpressionEvaluator_Förbjuden
ExpressionEvaluator_Förbjuden
    ACTION = Overwrite Existing Attributes
    ATTRLIST = ts_class
    EXPRESSION = 4
    -> network (writer GEOPACKAGE_2)
Note: Väg med hastighetsgräns >=90km/t
Junction_2
    -> ExpressionEvaluator_Olämplig
Note: Klass4 väg med hastighetsgräns >40km/t
Junction_5
    -> ExpressionEvaluator_Olämplig
ExpressionEvaluator_Olämplig
    ACTION = Overwrite Existing Attributes
    ATTRLIST = ts_class
    EXPRESSION = 3
    -> network (writer GEOPACKAGE_2)
ExpressionEvaluator_Tveksam
    ACTION = Overwrite Existing Attributes
    ATTRLIST = ts_class
    EXPRESSION = 2
    -> network (writer GEOPACKAGE_2)
Note: Klass4 väg med hastighetsgräns <=40km/t
Junction_7
    -> ExpressionEvaluator_God
Note: Ange trafiksäkerhetsklass "God=1", "Tveksam=2", "Olämplig=3", "Förbjuden=4"
ExpressionEvaluator_God
    ACTION = Overwrite Existing Attributes
    ATTRLIST = ts_class
    EXPRESSION = 1
    -> Tester_MycketGod

Bookmark: Outputs
Note: Oklassade vägar
Junction_9
    -> network (writer GEOPACKAGE_2)
network (writer GEOPACKAGE_2)
    attributes: route_id text(38), length text(200), from_measure double, to_measure double, road_type smallint, operator_type smallint, operator_name text, width double, flow mediumint, flow_id mediumint, surface smallint, max_speed smallint, gcm_type smallint, road_name text, road_class smallint, grade_type smallint, subsidy boolean, subsidy_from_date smallint, subsidy_to_date smallint, motorway boolean, motorroad boolean, cycleroad text(200), flow_real text(200), ts_class text(200), oneway smallint, road_access text, residential boolean, bicycle_restrict mediumint, bicycle_route text, bicycleroad boolean,
      from_vertex mediumint, to_vertex mediumint

Bookmark: Test för vägar utan ÅDT
Note: Alla vägar med hastighet på 90km/t eller högre, eller klass 0-3 klassas som olämpliga.
TestFilter_vägklass
    DEFAULT_VALUE = <UNFILTERED>
    TEST_LIST:
      "BOOL_OP,OR,COMPOSITE_TEST,""""""1 OR 2"""""",TEST_CLAUSE,NUM_TEST @Value(max_speed) >= 90
      NUM_TEST @Value(road_class) < 4",olämplig,"BOOL_OP,OR,COMPOSITE_TEST,""""""1"""""",TEST_CLAUSE,NUM_TEST @Value(max_speed) <= 30",<= 30,"BOOL_OP,AND,COMPOSITE_TEST,""""""1 AND 2"""""",TEST_CLAUSE,NUM_TEST @Value(road_class) = 4
      NUM_TEST @Value(max_speed) > 40",4 och > 40,"BOOL_OP,AND,COMPOSITE_TEST,""""""1 AND 2"""""",TEST_CLAUSE,NUM_TEST @Value(road_class) = 4
      NUM_TEST @Value(max_speed) <= 40",4 och <= 40,"BOOL_OP,OR,COMPOSITE_TEST,""""""1"""""",TEST_CLAUSE,NUM_TEST @Value(road_class) IN 5,6",5, 6,"BOOL_OP,OR,COMPOSITE_TEST,""""""1"""""",TEST_CLAUSE,NUM_TEST @Value(road_class) >= 7",7, 8, 9
    olämplig -> Junction
    <= 30 -> Junction_12
    4 och > 40 -> Junction_10
    4 och <= 40 -> ExpressionEvaluator_Tveksam
    5, 6 -> SpatialFilter [Candidate]
    7, 8, 9 -> ExpressionEvaluator_God
Note: ExpressionEvaluator_Olämplig : Input
Note: Trafiksäkerhetsklass för vägklass 5 och 6 beror på tätorts storlek och hastighetsgränsen. Vägklass 4 tar också hänsyn till hastighetsgränsen. Vägklass 0-3 och 7-9 klassas som olämplig respektive god.
Junction
    -> Junction_2
Junction_12
    -> Junction_11
Junction_10
    -> Junction_5
Tester_Befolkning
    BOOL_OP = OR
    COMPOSITE_TEST = 1
    TEST_CLAUSE = TEST @Value(BEF) >= 15000
    TEST_MODE = TEST
    PASSED -> SpatialFilter [Filter]
SpatialFilter
    AGGREGATE_HANDLING = Yes
    BASE_TYPE = Multiple Filters
    CURVE_BOUNDARY_RULE_PARAM = Default Rule
    PASS_CRITERIA = Pass Against One Filter
    PREDICATES = INTERSECTS
    USE_BOUNDING_BOX = No
    PASSED -> ExpressionEvaluator_Tveksam
    FAILED -> Tester_40kmt
Tester_40kmt
    BOOL_OP = OR
    COMPOSITE_TEST = 1
    TEST_CLAUSE = TEST @Value(max_speed) <= 40
    TEST_MODE = TEST
    PASSED -> Junction_6
    FAILED -> ExpressionEvaluator_Tveksam
Note: ExpressionEvaluator_God : Input
Junction_6
    -> Junction_7

Bookmark: Skapa trafiksäkerhetsklass "Mycket God"
Note: Hastighet <= 30 km/t utan ÅDT
Junction_11
    -> ExpressionEvaluator_MycketGod
Note: Vägar som klassas som "God=1" med ÅDT <= 250 eller med vägbredd <= 3,5 klassas om till "Mycket god=0".
Tester_MycketGod
    BOOL_OP = COMPOSITE
    COMPOSITE_TEST:
      ( NOT 1 AND ( 2 OR 3 )
       ) OR ( 4 AND 5 AND 6 )
    TEST_CLAUSE:
      TEST flow_real ATTRIBUTE_VALUE_NULL ""
      NUM_TEST @Value(flow_real) <= 250
      NUM_TEST @Value(width) <= 3.5
      TEST flow_real ATTRIBUTE_VALUE_NULL ""
      NUM_TEST @Value(max_speed) <= 30
      NUM_TEST @Value(road_class) IN 7,8,9
    TEST_MODE = PER_TEST
    PASSED -> ExpressionEvaluator_MycketGod
    FAILED -> network (writer GEOPACKAGE_2)
ExpressionEvaluator_MycketGod
    ACTION = Overwrite Existing Attributes
    ATTRLIST = ts_class
    EXPRESSION = 0
    -> network (writer GEOPACKAGE_2)
