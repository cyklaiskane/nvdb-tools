FME workspace cyklaiskane.fmw

Parameters:
- SourceDataset_ESRISHAPE_4 =   # SCB Tätort shapefil
- SourceDataset_NVDB_Merged =   # Homogeniserad NVDB data
- SourceDataset_NVDB_Region =   # NVDB Regionsfil
- SourceDataset_ADT_to_SDT =   # ÅDT till SDT data
- FeatureWriter_DATASET = cyklaiskane.gpkg   # Resultatfil

Readers:
- ESRISHAPE_1: ESRISHAPE from $(SourceDataset_ESRISHAPE_4)
- FILEGDB_1: FILEGDB from $(SourceDataset_NVDB_Merged)

Bookmark: Indata (Vägnät och tätorter)
Note: Egenskaper som måste finnas med i datasettet: / - Bro och tunnel/Konstruktion / - C - Rekommenderad bilväg för cykeltrafik / - C_Cykelled / - Driftbidrag statligt/Vägdelsnr / - Driftbidrag statligt/Vägnr / - Funktionell vägklass/Klass / - Färjeled / - Gatunamn/Namn / - GCM-vägtyp/GCM-typ / - Hastighetsgräns/Högsta tillåtna hastighet (Bakriktningen) / - Hastighetsgräns/Högsta tillåtna hastighet (Framriktningen) / - Motortrafikled / - Motorväg / - Slitlager/Slitlagertyp / - Trafik/ÅDT fordon / - Vägbredd/Bredd / - Väghållare/Väghållarnamn / - Väghållare/Väghållartyp / - Vägtrafiknät/Nättyp
skane_flat_partial_SKANE_LAN (reader FILEGDB_1)
    attributes: OBJECTID objectid, ROUTE_ID text(20), FROM_MEASURE double, TO_MEASURE double, Motortrafikled int, Motorvag int, konst_190 text(23), C_Cykelled int, C_Rekommenderad_bilvag_for_c int, Vagde_10379 text(0), Vagnr_10370 text(0), Klass_181 text(1), Farjeled int, F_Forbjuden_fardriktning int, B_Forbjuden_fardriktning int, F_Dagsl_449_833 text(39), B_Dagsl_449_833 text(39), Namn_130 text(2000), GCM_t_502 int, F_Hogst_225 text(10), B_Hogst_225 text(10), Slitl_152 text(6), TEN_T_489 text(0), TEN_T_488 text(0), ADT_f_117 text(0), Matar_121 text(0), slitl_25 text(15), Bredd_156 text(0), Vagha_7 text(2000), Vagha_6 text(8),
      Vagtr_474 int, vagty_41 text(24), Namn_132 text(2000), Shape_Length double
    -> AttributeKeeper
AttributeKeeper
    KEEP_ATTRS = Farjeled,Klass_181,B_Hogst_225,Namn_130,ADT_f_117,Motortrafikled,C_Cykelled,GCM_t_502,Bredd_156,F_Hogst_225,B_Forbjuden_fardriktning,Motorvag,Vagtr_474,TO_MEASURE,Vagnr_10370,konst_190,Vagha_6,FROM_MEASURE,Vagha_7,Vagde_10379,ROUTE_ID,F_Forbjuden_fardriktning,OBJECTID,C_Rekommenderad_bilvag_for_c,Shape_Length,Slitl_152
    -> AttributeManager_2
AttributeManager_2
    ATTR_TABLE:
      SET_TO F_Hogst_225 = FME_CONDITIONAL:DEFAULT_VALUE'_FME_NO_OP_'BOOL_OP;OR;COMPOSITE_TEST;1;TEST @Value(F_Hogst_225) = gångfart'5'FME_NUM_CONDITIONS2___
      SET_TO B_Hogst_225 = FME_CONDITIONAL:DEFAULT_VALUE'_FME_NO_OP_'BOOL_OP;OR;COMPOSITE_TEST;1;TEST @Value(B_Hogst_225) = gångfart'5'FME_NUM_CONDITIONS2___
      SET_TO TS_klass = FME_NULL_VALUE
    -> ExpressionEvaluator
ExpressionEvaluator
    ACTION = Create New Attribute
    EXPRESSION = @max(@Value(F_Hogst_225), @Value(B_Hogst_225))
    VAL_ATTR = Hogst_225
    -> TestFilter_2
Creator
    GEOMTYPE = Geometry Object
    NUM = 1
    CREATED -> Tester
Note: Både NVDB region och ÅDT till SDT måste vara definerade för att aktivera läsarna
Tester
    BOOL_OP = COMPOSITE
    COMPOSITE_TEST = 1 AND 2
    TEST_CLAUSE:
      CASE_INSENSITIVE_TEST $(SourceDataset_ADT_to_SDT) ENDS_WITH .xlsx
      CASE_INSENSITIVE_TEST $(SourceDataset_NVDB_Region) ENDS_WITH .gdb
    TEST_MODE = TEST
    PASSED -> ADT_to_SDT [INITIATOR]
    PASSED -> NVDB_Trafik [INITIATOR]
NVDB_Trafik: FeatureReader
    ATTRS_TO_EXPOSE = OBJECTID ROUTE_ID Avsni_119
    ATTR_ACCUM_MODE = Only Use Result
    COMBINE_GEOM = Use Result
    DATASET = $(SourceDataset_NVDB_Region)
    FEATURETYPES = TNE_FT_Trafik_4
    FILEGDB_QUERY_FEATURE_TYPES_FOR_MERGE_FILTERS = Yes
    FILEGDB_SIMPLE_DONUT_GEOMETRY = simple
    FILEGDB_STRIP_GUID_GLOBALID_BRACES = no
    FILEGDB_USE_SEARCH_ENVELOPE = NO
    FORMAT = FILEGDB
    INTERACT = <No Spatial Filter>
    OUTPUT_FEATURES_DISPLAY = Schema and Data Features
    <OTHER> -> InlineQuerier_Beräkna_SDT [TNE_FT_Trafik_4]
ADT_to_SDT: FeatureReader
    ATTRS_TO_EXPOSE = AVSN_ID IK_NR
    ATTR_ACCUM_MODE = Only Use Result
    COMBINE_GEOM = Use Result
    DATASET = $(SourceDataset_ADT_to_SDT)
    FORMAT = XLSXR
    INTERACT = <No Spatial Filter>
    OUTPUT_FEATURES_DISPLAY = Schema and Data Features
    XLSXR_ALLOW_DOLLAR_SIGNS = YES
    XLSXR_CASE_SENSITIVE_FEATURE_TYPES = YES
    XLSXR_CREATE_FEATURE_TABLES_FROM_DATA = Yes
    XLSXR_EXCEL_COL_NAMES = YES
    XLSXR_EXPAND_MERGED_CELLS = Yes
    XLSXR_FORCE_DATETIME = NO
    XLSXR_QUERY_FEATURE_TYPES_FOR_MERGE_FILTERS = Yes
    XLSXR_READ_BLANK_AS = Missing
    XLSXR_SCAN_SCHEMA_IF_DYNAMIC = No
    XLSXR_STRIP_SHEETNAME_SPACES = YES
    XLSXR_USE_SCHEMA_OTHER_FILES = No
    <OTHER> -> InlineQuerier_Beräkna_SDT [SDT]
To2015_Swe99TM (reader ESRISHAPE_1)
    attributes: OBJECTID long, AR char(4), LANSKOD char(2), AREA_HA long, BEF long, KOMMUNKOD char(4), KOMMUNNAMN char(50), TATORTSKOD char(5), TATORT char(50), LAN_NAMN char(50)
    -> Tester_Befolkning

Bookmark: Testfiltrar
TestFilter_2
    DEFAULT_VALUE = <UNFILTERED>
    TEST_LIST:
      "BOOL_OP,OR,COMPOSITE_TEST,""""""1"""""",TEST_CLAUSE,TEST @Value(Farjeled) = 1",färjeled,"BOOL_OP,OR,COMPOSITE_TEST,""""""1 OR 2"""""",TEST_CLAUSE,CASE_INSENSITIVE_TEST @Value(Vagtr_474) = 2
      CASE_INSENSITIVE_TEST @Value(Vagtr_474) = 4",cykelväg,"BOOL_OP,OR,COMPOSITE_TEST,""""""1 OR 2"""""",TEST_CLAUSE,NUM_TEST @Value(Motorvag) = 1
      NUM_TEST @Value(Motortrafikled) = 1",cykelförbud,"BOOL_OP,AND,COMPOSITE_TEST,""""""1 AND 2 AND 3 AND 4"""""",TEST_CLAUSE,TEST Vagde_10379 ATTRIBUTE_VALUE_NULL ""
      TEST Vagnr_10370 ATTRIBUTE_VALUE_NULL ""
      TEST @Value(Vagha_6) = enskild
      TEST @Value(Slitl_152) = grus",oklassificerade grusvägar,"BOOL_OP,AND,COMPOSITE_TEST,""""""1 AND 2"""""",TEST_CLAUSE,CASE_INSENSITIVE_TEST @Value(Vagtr_474) = 1
      TEST Hogst_225 ATTRIBUTE_VALUE_NULL """,allmän väg utan hastighet,"BOOL_OP,OR,COMPOSITE_TEST,""""""1"""""",TEST_CLAUSE,TEST ADT_f_117 ATTRIBUTE_HAS_A_VALUE """,har ÅDT
    färjeled -> Junction_8
    cykelväg -> TestFilter
    cykelförbud -> Junction_3
    oklassificerade grusvägar -> Junction_14
    allmän väg utan hastighet -> Junction_8
    har ÅDT -> FeatureJoiner [LEFT]
    <UNFILTERED> -> TestFilter_vägklass
Note: Direkt ut
Junction_8
    -> Junction_9
Note: Direkt till B5
Junction_3
    -> Junction_4
Note: Direkt till G2
Junction_14
    -> AttributeManager_G2

Bookmark: Cykelvägsklassning
TestFilter
    DEFAULT_VALUE = Cykelväg (C1)
    TEST_LIST = "BOOL_OP,OR,COMPOSITE_TEST,""""""1"""""",TEST_CLAUSE,TEST @Value(Vagtr_474) = 4",Gångväg,"BOOL_OP,OR,COMPOSITE_TEST,""""""1"""""",TEST_CLAUSE,TEST @Value(GCM_t_502) = 2",Cykelfält (C3),"BOOL_OP,OR,COMPOSITE_TEST,""""""1"""""",TEST_CLAUSE,TEST @Value(Slitl_152) = grus",Cykelväg, grus (C2)
    Gångväg -> Junction_13
    Cykelfält (C3) -> AttributeManager_C3
    Cykelväg, grus (C2) -> AttributeManager_C2
    Cykelväg (C1) -> AttributeManager_C1
AttributeManager_C3
    ATTR_TABLE = SET_TO TS_klass = C3
    -> Junction_13
AttributeManager_C2
    ATTR_TABLE = SET_TO TS_klass = C2
    -> Junction_13
AttributeManager_C1
    ATTR_TABLE = SET_TO TS_klass = C1
    -> Junction_13

Bookmark: Outputs
Note: Oklassade vägar
Junction_9
    -> Junction_13
Junction_13
    -> AttributeKeeper_2
AttributeKeeper_2
    KEEP_ATTRS = Farjeled,Klass_181,B_Hogst_225,Namn_130,ADT_f_117,Motortrafikled,C_Cykelled,GCM_t_502,Bredd_156,F_Hogst_225,B_Forbjuden_fardriktning,Motorvag,Vagtr_474,TO_MEASURE,Vagnr_10370,konst_190,Vagha_6,FROM_MEASURE,Vagha_7,Vagde_10379,ROUTE_ID,TS_klass,F_Forbjuden_fardriktning,OBJECTID,C_Rekommenderad_bilvag_for_c,Shape_Length,Slitl_152
    -> FeatureWriter [Output]

Bookmark: Ange trafiksäkerhetsklass
Junction_4
    -> AttributeManager_B5
AttributeManager_B5
    ATTR_TABLE = SET_TO TS_klass = B5
    -> Tester_grusväg_dålig
Note: Väg med hastighetsgräns >=90km/t
Junction_2
    -> AttributeManager_B4
Note: Klass4 väg med hastighetsgräns >40km/t
Junction_5
    -> AttributeManager_B4
AttributeManager_B4
    ATTR_TABLE = SET_TO TS_klass = B4
    -> Tester_grusväg_dålig
AttributeManager_B3
    ATTR_TABLE = SET_TO TS_klass = B3
    -> Tester_grusväg_dålig
Tester_grusväg_dålig
    BOOL_OP = OR
    COMPOSITE_TEST = 1
    TEST_CLAUSE = TEST @Value(Slitl_152) = grus
    TEST_MODE = TEST
    PASSED -> AttributeManager_G2
    FAILED -> Junction_13
AttributeManager_G2
    ATTR_TABLE = SET_TO TS_klass = G2
    -> Junction_13
Note: Klass4 väg med hastighetsgräns <=40km/t
Junction_7
    -> AttributeManager_B2
Note: Ange trafiksäkerhetsklass "God=1", "Tveksam=2", "Olämplig=3", "Förbjuden=4"
AttributeManager_B2
    ATTR_TABLE = SET_TO TS_klass = B2
    -> Tester_MycketGod
Tester_grusväg_bra
    BOOL_OP = OR
    COMPOSITE_TEST = 1
    TEST_CLAUSE = TEST @Value(Slitl_152) = grus
    TEST_MODE = TEST
    PASSED -> AttributeManager_G1
    FAILED -> Junction_13
AttributeManager_G1
    ATTR_TABLE = SET_TO TS_klass = G1
    -> Junction_13

Bookmark: Test för vägar utan ÅDT
Note: Alla vägar med hastighet på 90km/t eller högre, eller klass 0-3 klassas som olämpliga.
TestFilter_vägklass
    DEFAULT_VALUE = <UNFILTERED>
    TEST_LIST:
      "BOOL_OP,OR,COMPOSITE_TEST,""""""1 OR 2"""""",TEST_CLAUSE,NUM_TEST @Value(Hogst_225) >= 90
      NUM_TEST @Value(Klass_181) < 4",olämplig,"BOOL_OP,OR,COMPOSITE_TEST,""""""1"""""",TEST_CLAUSE,NUM_TEST @Value(Hogst_225) <= 30",<= 30,"BOOL_OP,AND,COMPOSITE_TEST,""""""1 AND 2"""""",TEST_CLAUSE,NUM_TEST @Value(Klass_181) = 4
      NUM_TEST @Value(Hogst_225) > 40",4 och > 40,"BOOL_OP,AND,COMPOSITE_TEST,""""""1 AND 2"""""",TEST_CLAUSE,NUM_TEST @Value(Klass_181) = 4
      NUM_TEST @Value(Hogst_225) <= 40",4 och <= 40,"BOOL_OP,OR,COMPOSITE_TEST,""""""1"""""",TEST_CLAUSE,NUM_TEST @Value(Klass_181) IN 5,6",5, 6,"BOOL_OP,OR,COMPOSITE_TEST,""""""1"""""",TEST_CLAUSE,NUM_TEST @Value(Klass_181) >= 7",7, 8, 9
    olämplig -> Junction
    <= 30 -> Junction_12
    4 och > 40 -> Junction_10
    4 och <= 40 -> AttributeManager_B3
    5, 6 -> SpatialFilter [Candidate]
    7, 8, 9 -> AttributeManager_B2
Note: ExpressionEvaluator_Olämplig : Input
Note: Trafiksäkerhetsklass för vägklass 5 och 6 beror på tätorts storlek och hastighetsgränsen. Vägklass 4 tar också hänsyn till hastighetsgränsen. Vägklass 0-3 och 7-9 klassas som olämplig respektive god.
Junction
    -> Junction_2
Junction_12
    -> Junction_11
Junction_10
    -> Junction_5
Tester_Befolkning
    BOOL_OP = OR
    COMPOSITE_TEST = 1
    TEST_CLAUSE = TEST @Value(BEF) >= 15000
    TEST_MODE = TEST
    PASSED -> SpatialFilter [Filter]
SpatialFilter
    AGGREGATE_HANDLING = Yes
    BASE_TYPE = Multiple Filters
    CURVE_BOUNDARY_RULE_PARAM = Default Rule
    PASS_CRITERIA = Pass Against One Filter
    PREDICATES = INTERSECTS
    USE_BOUNDING_BOX = No
    PASSED -> AttributeManager_B3
    FAILED -> Tester_40kmt
Tester_40kmt
    BOOL_OP = OR
    COMPOSITE_TEST = 1
    TEST_CLAUSE = TEST @Value(Hogst_225) <= 40
    TEST_MODE = TEST
    PASSED -> Junction_6
    FAILED -> AttributeManager_B3
Note: ExpressionEvaluator_God : Input
Junction_6
    -> Junction_7

Bookmark: Skapa trafiksäkerhetsklass "Mycket God"
Note: Hastighet <= 30 km/t utan ÅDT
Junction_11
    -> AttributeManager_B1
Note: Vägar som klassas som "God=1" med ÅDT <= 250 eller med vägbredd <= 3,5 klassas om till "Mycket god=0".
Tester_MycketGod
    BOOL_OP = COMPOSITE
    COMPOSITE_TEST:
      ( NOT 1 AND ( 2 OR 3 )
       ) OR ( 4 AND 5 AND 6 )
    TEST_CLAUSE:
      TEST ADT_f_117 ATTRIBUTE_VALUE_NULL ""
      NUM_TEST @Value(ADT_f_117) <= 250
      NUM_TEST @Value(Bredd_156) <= 3.5
      TEST ADT_f_117 ATTRIBUTE_VALUE_NULL ""
      NUM_TEST @Value(Hogst_225) <= 30
      NUM_TEST @Value(Klass_181) IN 7,8,9
    TEST_MODE = PER_TEST
    PASSED -> AttributeManager_B1
    FAILED -> Tester_grusväg_bra
AttributeManager_B1
    ATTR_TABLE = SET_TO TS_klass = B1
    -> Tester_grusväg_bra

Bookmark: Test för vägar med ÅDT
InlineQuerier_Beräkna_SDT
    QUERY_DEF:
      network,SELECT
          b.ROUTE_ID,
          max((IK_NR % 100) / 10.0) as ADT_to_SDT
      FROM
          "SDT" a
      JOIN
          "TNE_FT_Trafik_4" b
      ON
          a.AVSN_ID = b.Avsni_119
      WHERE
          IK_NR < 90000
      GROUP BY
          b.ROUTE_ID,FIRST
    QUERY_SCHEMA = network,ROUTE_ID,varchar(38),ADT_to_SDT,
    TABLE_DEF = SDT,AVSN_ID,integer,IK_NR,integer,TNE_FT_Trafik_4,OBJECTID,integer,Avsni_119,integer,ROUTE_ID,varchar(38)
    network -> FeatureJoiner [RIGHT]
FeatureJoiner
    ATTR_CONFLICT_RES = Use Left
    GEOMETRY_HANDLING = Use Left
    JOIN_KEYS = ROUTE_ID ROUTE_ID AUTO
    JOIN_MODE = Left
    JOINED -> ExpressionEvaluator_2
ExpressionEvaluator_2
    ACTION = Overwrite Existing Attributes
    ATTRLIST = ADT_f_117
    EXPRESSION = @round(@Value(ADT_f_117) * @Value(ADT_to_SDT))
    -> TestFilter_lämplighet
Note: Klassningen använder sig av Trafikverkets riktlinjer för vägvisning.
TestFilter_lämplighet
    DEFAULT_VALUE = god (B2)
    TEST_LIST:
      "BOOL_OP,COMPOSITE,COMPOSITE_TEST,""""""1 OR ( 2 AND 3 ) OR ( 4 AND 5 ) OR ( 6 AND 7 )"""""",TEST_CLAUSE,NUM_TEST @Value(Hogst_225) > 80
      NUM_TEST @Value(ADT_f_117) >= 2500
      NUM_TEST @Value(Hogst_225) > 40
      NUM_TEST @Value(ADT_f_117) >= 2000
      NUM_TEST @Value(Hogst_225) > 60
      NUM_TEST @Value(ADT_f_117) >= 1000
      NUM_TEST @Value(Hogst_225) > 70",olämplig (B4),"BOOL_OP,COMPOSITE,COMPOSITE_TEST,""""""1 OR ( 2 AND 3 ) OR ( 4 AND 5 ) OR ( 6 AND 7 )"""""",TEST_CLAUSE,NUM_TEST @Value(Hogst_225) > 70
      NUM_TEST @Value(ADT_f_117) >= 1000
      NUM_TEST @Value(Hogst_225) > 60
      NUM_TEST @Value(ADT_f_117) >= 2000
      NUM_TEST @Value(Hogst_225) > 40
      NUM_TEST @Value(ADT_f_117) >= 2500
      NUM_TEST @Value(Hogst_225) > 30",tveksam (B3)
    olämplig (B4) -> AttributeManager_B4
    tveksam (B3) -> AttributeManager_B3
    god (B2) -> AttributeManager_B2

Bookmark: GPKG Writer
FeatureWriter
    COORDSYS = EPSG:3006
    DATASET = $(FeatureWriter_DATASET)
    DATASET_ATTR = _dataset
    FEATURE_TYPE_LIST_ATTR = _feature_type
    FORMAT = GEOPACKAGE
    GEOPACKAGE_COORDINATE_SYSTEM_GRANULARITY = FEATURE_TYPE
    GEOPACKAGE_DESTINATION_DATASETTYPE_VALIDATION = Yes
    GEOPACKAGE_ENCODE_FEATURE_TYPE_AND_ATTR_NAMES = YES
    GEOPACKAGE_OVERWRITE_DATASET = YES
    GEOPACKAGE_TRANSACTION_SIZE = 10000
    GEOPACKAGE_WRITE_NULLS = YES
    TOTAL_FEATURES_WRITTEN_ATTR = _total_features_written
    SUMMARY -> PythonCaller
PythonCaller
    PYTHONSOURCE:
      import fme
      import fmeobjects
      import sqlite3


      class FeatureProcessor(object):
          def __init__(self):
              pass
          def input(self,feature):
              db_file = feature.getAttribute("_dataset")
              with sqlite3.connect(db_file) as db:
                  db.executescript("""
      CREATE VIEW IF NOT EXISTS
        cykelnat (id,geom,route_id,from_measure,to_measure,ts_klass) AS
      SELECT id,geom,route_id,from_measure,to_measure,ts_klass
      FROM network
      WHERE vagtr_474 = 2;

      INSERT OR REPLACE INTO
        gpkg_contents (table_name,data_type,identifier,min_x,min_y,max_x,max_y,srs_id)
      SELECT "cykelnat",data_type,"cykelnat",min_x,min_y,max_x,max_y,srs_id
      FROM gpkg_contents
      WHERE identifier = "network";

      INSERT OR REPLACE INTO
        gpkg_geometry_columns (table_name,column_name,geometry_type_name,srs_id,z,m)
      SELECT "cykelnat","geom",geometry_type_name,srs_id,z,m
      FROM gpkg_geometry_columns
      WHERE table_name = "network";
      """)

                  db.executescript("""
      CREATE VIEW IF NOT EXISTS
        vagnat (id,geom,route_id,from_measure,to_measure,ts_klass) AS
      SELECT id,geom,route_id,from_measure,to_measure,ts_klass
      FROM network
      WHERE vagtr_474 = 1;

      INSERT OR REPLACE INTO
        gpkg_contents (table_name,data_type,identifier,min_x,min_y,max_x,max_y,srs_id)
      SELECT "vagnat",data_type,"vagnat",min_x,min_y,max_x,max_y,srs_id
      FROM gpkg_contents
      WHERE identifier = "network";

      INSERT OR REPLACE INTO
        gpkg_geometry_columns (table_name,column_name,geometry_type_name,srs_id,z,m)
      SELECT "vagnat","geom",geometry_type_name,srs_id,z,m
      FROM gpkg_geometry_columns
      WHERE table_name = "network";
      """)

                  db.executescript("""
      CREATE VIEW IF NOT EXISTS
        bro_tunnel (id,geom,route_id,from_measure,to_measure,ts_klass) AS
      SELECT id,geom,route_id,from_measure,to_measure,ts_klass
      FROM network
      WHERE konst_190 LIKE "%fart";

      INSERT OR REPLACE INTO
        gpkg_contents (table_name,data_type,identifier,min_x,min_y,max_x,max_y,srs_id)
      SELECT "bro_tunnel",data_type,"bro_tunnel",min_x,min_y,max_x,max_y,srs_id
      FROM gpkg_contents
      WHERE identifier = "network";

      INSERT OR REPLACE INTO
        gpkg_geometry_columns (table_name,column_name,geometry_type_name,srs_id,z,m)
      SELECT "bro_tunnel","geom",geometry_type_name,srs_id,z,m
      FROM gpkg_geometry_columns
      WHERE table_name = "network";
      """)

                  db.executescript("""
      CREATE VIEW IF NOT EXISTS
        farjeled (id,geom,route_id,from_measure,to_measure,ts_klass) AS
      SELECT id,geom,route_id,from_measure,to_measure,ts_klass
      FROM network
      WHERE farjeled = 1;

      INSERT OR REPLACE INTO
        gpkg_contents (table_name,data_type,identifier,min_x,min_y,max_x,max_y,srs_id)
      SELECT "farjeled",data_type,"farjeled",min_x,min_y,max_x,max_y,srs_id
      FROM gpkg_contents
      WHERE identifier = "network";

      INSERT OR REPLACE INTO
        gpkg_geometry_columns (table_name,column_name,geometry_type_name,srs_id,z,m)
      SELECT "farjeled","geom",geometry_type_name,srs_id,z,m
      FROM gpkg_geometry_columns
      WHERE table_name = "network";
      """)
              self.pyoutput(feature)
          def close(self):
              pass
    PYTHONSYMBOL = FeatureProcessor
    -> PythonCaller_Output
PythonCaller_Output: Inspector
